ConsumerState DEFINITIONS AUTOMATIC TAGS ::=
BEGIN

  GenerationProgress ::= SEQUENCE {
    shard OCTET STRING,
    generation INTEGER
  }

  StreamBufferProgress ::= CHOICE {
    finished NULL,
    active ActiveStreamBufferProgress
  }

  ActiveStreamBufferProgress ::= SEQUENCE {
    it OCTET STRING,
    lastMessageId INTEGER OPTIONAL,
    unacked SEQUENCE OF INTEGER
  }

  StreamProgress ::= SEQUENCE {
    shard OCTET STRING,
    generation INTEGER,
    stream OCTET STRING,
    bufferProgress StreamBufferProgress
  }

  Progress ::= SEQUENCE {
    generationProgress SEQUENCE OF GenerationProgress,
    streamProgress SEQUENCE OF StreamProgress
  }

  ConsumerStateV1 ::= SEQUENCE {
    progress Progress
  }

  ConsumerState ::= CHOICE {
    v1 ConsumerStateV1
  }
END
