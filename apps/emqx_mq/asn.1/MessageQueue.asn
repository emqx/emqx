MessageQueue DEFINITIONS ::=
BEGIN

  StreamBufferProgress ::= SEQUENCE {
    it [0] OCTET STRING,
    lastMessageId [1] INTEGER OPTIONAL,
    unacked [2] SEQUENCE OF INTEGER
  }

  FinishedShardProgress ::= SEQUENCE {
    generation [0] INTEGER
  }

  ActiveShardProgress ::= SEQUENCE {
    generation [0] INTEGER,
    stream [1] OCTET STRING,
    bufferProgress [2] StreamBufferProgress
  }

  ShardProgress ::= SEQUENCE {
    progress [0] CHOICE {
      active [0] ActiveShardProgress,
      finished [1] FinishedShardProgress
    },
    ...
  }

  Limits ::= SEQUENCE {
    maxShardMessageCount [0] INTEGER OPTIONAL,
    maxShardMessageBytes [1] INTEGER OPTIONAL
  }

  MQ ::= SEQUENCE {
    id [0] OCTET STRING,
    topicFilter [1] OCTET STRING,
    isLastvalue [2] BOOLEAN,
    consumerMaxInactive [3] INTEGER,
    pingInterval [4] INTEGER,
    redispatchInterval [5] INTEGER,
    dispatchStrategy [6] OCTET STRING,
    localMaxInflight [7] INTEGER,
    busySessionRetryInterval [8] INTEGER,
    streamMaxBufferSize [9] INTEGER,
    streamMaxUnacked [10] INTEGER,
    consumerPersistenceInterval [11] INTEGER,
    dataRetentionPeriod [12] INTEGER,
    keyExpression [13] OCTET STRING OPTIONAL,
    limits [14] Limits OPTIONAL,
    name [15] OCTET STRING OPTIONAL,
    deliverCutoffDate [16] INTEGER OPTIONAL,
    onFull [17] OCTET STRING OPTIONAL,
    ...
  }

  StorageIndexRecord ::= SEQUENCE {
    tsUs [0] INTEGER,
    value [1] INTEGER
  }

  SerialIndexBucket ::= SEQUENCE {
    tsUs [0] INTEGER,
    serial [1] INTEGER,
    bytes [2] INTEGER,
    count [3] INTEGER,
    ...
  }

  StorageIndex ::= SEQUENCE {
    maxTsUs [0] INTEGER,
    count [1] SEQUENCE OF StorageIndexRecord OPTIONAL,
    bytes [2] SEQUENCE OF StorageIndexRecord OPTIONAL,
    serialBuckets [3] SEQUENCE OF SerialIndexBucket OPTIONAL,
    seenFenceSerial [4] INTEGER OPTIONAL,
    releasedBeforeUs [5] INTEGER OPTIONAL,
    ...
  }

END
