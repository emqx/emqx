ConsumerClaim DEFINITIONS AUTOMATIC TAGS ::=
BEGIN
  -- Pid of the consumer process
  ConsumerRef ::= OCTET STRING

  LastSeenTimestamp ::= INTEGER

  ConsumerClaimV1 ::= SEQUENCE {
    consumerRef ConsumerRef,
    lastSeenTimestamp LastSeenTimestamp
  }

  ConsumerClaim ::= CHOICE {
    v0 ConsumerClaimV1,
    ...
  }
END
