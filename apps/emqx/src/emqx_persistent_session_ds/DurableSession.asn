DurableSession DEFINITIONS ::=
BEGIN
  ID ::= INTEGER(0..MAX)

  TopicFilter ::= SEQUENCE {
    topic [0] OCTET STRING,
    group [1] OCTET STRING OPTIONAL
  }

  Subscription ::= SEQUENCE {
    id [0] ID,
    currentState [1] ID,
    startTime [2] INTEGER,
    ...
  }

  Misc ::= SEQUENCE {
    key [0] OCTET STRING,
    val [1] OCTET STRING
  }

  FilterOp ::= ENUMERATED {
    eq(0),
    gt(1),
    lt(2),
    gte(3),
    lte(4),
    ...
  }

  FilterClause ::= SEQUENCE {
    op [0] FilterOp,
    key [1] OCTET STRING,
    stringValue [2] OCTET STRING OPTIONAL,
    numberValue [3] REAL OPTIONAL,
    ...
  }

  SubscriptionFilter ::= SEQUENCE {
    raw [0] OCTET STRING,
    source [1] OCTET STRING,
    clauses [2] SEQUENCE OF FilterClause,
    ...
  }

  SubState ::= SEQUENCE {
    parentSub [0] ID,
    -- Flags
    upgradeQos [1] BOOLEAN,
    durable [2] BOOLEAN,
    --
    supersededBy [3] ID OPTIONAL,
    shareTopicFilter [4] TopicFilter OPTIONAL,
    --
    miscSubopts [5] SEQUENCE OF Misc,
    subscriptionFilter [6] SubscriptionFilter OPTIONAL,
    ...
  }

  StreamKey ::= SEQUENCE {
    subId [0] ID,
    stream [1] OCTET STRING
  }

  SRS ::= SEQUENCE {
    shard [0] OCTET STRING,
    generation [1] INTEGER,
    itBegin [2] OCTET STRING,
    -- Strictly speaking, we don't have to store itEnd, as can be
    -- derived from batchSize and itBegin. It's used as for some
    -- checks, so it's worth having.
    itEnd [3] OCTET STRING OPTIONAL,
    batchSize [4] INTEGER,
    firstSeqNoQoS1 [5] INTEGER,
    firstSeqNoQoS2 [6] INTEGER,
    lastSeqNoQoS1 [7] INTEGER,
    lastSeqNoQoS2 [8] INTEGER,
    unsubscribed [9] BOOLEAN,
    subscriptionState [10] ID,
    ...
  }
END
