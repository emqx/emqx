--------------------------------------------------------------------------
-- Copyright (c) 2025 EMQ Technologies Co., Ltd. All Rights Reserved.
--------------------------------------------------------------------------

DSBuiltinSLSkipstreamV1 DEFINITIONS AUTOMATIC TAGS ::=
BEGIN
  EXPORTS ALL;

  IteratorSkipstreamLTSV1 ::= SEQUENCE {
    static OCTET STRING,
    lastKey INTEGER,
    compressedTf OCTET STRING
  }
END
