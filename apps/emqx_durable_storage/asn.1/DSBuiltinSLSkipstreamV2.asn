--------------------------------------------------------------------------
-- Copyright (c) 2025 EMQ Technologies Co., Ltd. All Rights Reserved.
--------------------------------------------------------------------------

DSBuiltinSLSkipstreamV2 DEFINITIONS AUTOMATIC TAGS ::=
BEGIN
  EXPORTS ALL;
  IMPORTS TopicFilter FROM DSMetadataCommon;

  -- Iterator metadata.
  Iterator ::= SEQUENCE {
    static OCTET STRING,
    topicFilter TopicFilter
  }
END
